FME workspace combiner.fmw

Parameters:
- SourceDataset_CSV2 = ../models/building/lod2/tiles/citygml/correspondances.csv   # Source CSV (Comma Separated Value) File(s)
- SourceDataset_CITYGML = ../models/building/lod2/tiles/citygml/*.gml.gz   # Source CityGML File(s)
- DestDataset_CITYGML = ../models/building/lod2/combined/citygml/lod2_building_models.gml   # Destination CityGML Document
- DestDataset_CITYGML_3 = ../models/building/lod3/combined/citygml/lod3_building_models.gml   # Destination CityGML Document
- SourceDataset_CITYGML_2 = ""../models/models/building/lod3/individual/citygml/**/*.gml" "../models/building/lod3/individual/citygml/**/*.xml""   # Source CityGML File(s)

Readers:
- CSV2_1: CSV2 from $(SourceDataset_CSV2)
- CITYGML_1: CITYGML from $(SourceDataset_CITYGML)
- CITYGML_5: CITYGML from $(SourceDataset_CITYGML_2)

Writers:
- CITYGML_2: CITYGML to $(DestDataset_CITYGML)
- CITYGML_4: CITYGML to $(DestDataset_CITYGML_3)

Bookmark: Combination of the LOD3 models
BuildingInstallation (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, materialUncertainty xml_buffer, @cityeditor:layer xml_buffer, frameMaterialClass xml_buffer, klumMaterialClass xml_buffer, klumMaterialIndex xml_buffer, materialClass xml_buffer, materialName xml_buffer,
      paneMaterialClass xml_buffer
    -> GeometryFilter
OuterCeilingSurface (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, klumMaterialClass xml_buffer, klumMaterialIndex xml_buffer, materialUncertainty xml_buffer
    -> GeometryFilter
OuterFloorSurface (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, materialUncertainty xml_buffer, klumMaterialClass xml_buffer, klumMaterialIndex xml_buffer, materialClass xml_buffer, materialName xml_buffer
    -> GeometryFilter
Building (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, ade_noise_building_apartments xml_uint64, ade_noise_building_inhabitants xml_uint64, ade_noise_building_emission_points xml_buffer, ade_noise_building_Leq_day xml_real64, ade_noise_building_Leq_day_units xml_buffer, ade_noise_building_Lmax_day xml_real64, ade_noise_building_Lmax_day_units xml_buffer, ade_noise_building_Lmin_day xml_real64, ade_noise_building_Lmin_day_units xml_buffer, ade_noise_building_Leq_night xml_real64, ade_noise_building_Leq_night_units xml_buffer, ade_noise_building_Lmax_night xml_real64, ade_noise_building_Lmax_night_units xml_buffer, ade_noise_building_Lmin_night xml_real64, ade_noise_building_Lmin_night_units xml_buffer, ade_noise_building_reflection xml_buffer, ade_noise_building_reflection_correction xml_real64, ade_noise_building_reflection_correction_units xml_buffer, ade_noise_building_remark xml_buffer, dataAvailable xml_buffer,
      CreationDate xml_buffer, DataAvailable xml_buffer, creationDate xml_buffer, opendrive_dynamic xml_buffer, opendrive_id xml_buffer, opendrive_identifier_modelDate xml_buffer, opendrive_identifier_modelName xml_buffer, opendrive_identifier_modelVendor xml_buffer, opendrive_identifier_roadId xml_buffer, opendrive_identifier_roadObjectId xml_buffer, opendrive_identifier_roadObjectName xml_buffer, opendrive_identifier_sourceFileHashSha256 xml_buffer, opendrive_identifier_sourceFileName xml_buffer, opendrive_name xml_buffer, opendrive_orientation xml_buffer, opendrive_roadObject_dynamic xml_buffer, opendrive_roadObject_orientation xml_buffer, opendrive_roadObject_type xml_buffer, opendrive_road_length xml_buffer, opendrive_road_rule xml_buffer, opendrive_type xml_buffer
    -> GeometryFilter
BuildingPart (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, ade_noise_building_apartments xml_uint64, ade_noise_building_inhabitants xml_uint64, ade_noise_building_emission_points xml_buffer, ade_noise_building_Leq_day xml_real64, ade_noise_building_Leq_day_units xml_buffer, ade_noise_building_Lmax_day xml_real64, ade_noise_building_Lmax_day_units xml_buffer, ade_noise_building_Lmin_day xml_real64, ade_noise_building_Lmin_day_units xml_buffer, ade_noise_building_Leq_night xml_real64, ade_noise_building_Leq_night_units xml_buffer, ade_noise_building_Lmax_night xml_real64, ade_noise_building_Lmax_night_units xml_buffer, ade_noise_building_Lmin_night xml_real64, ade_noise_building_Lmin_night_units xml_buffer, ade_noise_building_reflection xml_buffer, ade_noise_building_reflection_correction xml_real64, ade_noise_building_reflection_correction_units xml_buffer, ade_noise_building_remark xml_buffer, klumMaterialClass xml_buffer,
      klumMaterialIndex xml_buffer, materialUncertainty xml_buffer
    -> GeometryFilter
CityModel (reader CITYGML_5)
    attributes: citygml_target_uri xml_buffer, gml_description xml_buffer, gml_name xml_buffer, citygml_city_object_member{}.xlink_href xml_buffer, citygml_appearance_member{}.xlink_href xml_buffer, gml_feature_member{}.xlink_href xml_buffer
    -> GeometryFilter
Door (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_address{}.xlink_href xml_buffer, @cityeditor:layer xml_buffer, frameMaterialClass xml_buffer, frameMaterialName xml_buffer, frameMaterialUncertainty xml_buffer, paneMaterialClass xml_buffer, frameKlumMaterialClass xml_buffer, frameKlumMaterialIndex xml_buffer, klumMaterialClass xml_buffer, klumMaterialIndex xml_buffer, materialClass xml_buffer, materialName xml_buffer, materialUncertainty xml_buffer
    -> GeometryFilter
GroundSurface (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, klumMaterialClass xml_buffer, klumMaterialIndex xml_buffer, materialUncertainty xml_buffer
    -> GeometryFilter
RoofSurface (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, klumMaterialClass xml_buffer, klumMaterialIndex xml_buffer, materialClass xml_buffer, materialName xml_buffer, materialUncertainty xml_buffer
    -> GeometryFilter
WallSurface (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, klumMaterialClass xml_buffer, klumMaterialIndex xml_buffer, materialUncertainty xml_buffer, materialClass xml_buffer, materialName xml_buffer
    -> GeometryFilter
Window (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, frameKlumMaterialClass xml_buffer, frameKlumMaterialIndex xml_buffer, frameMaterialClass xml_buffer, frameMaterialName xml_buffer, frameMaterialUncertainty xml_buffer, paneMaterialClass xml_buffer, @cityeditor:layer xml_buffer, materialClass xml_buffer, materialName xml_buffer, materialUncertainty xml_buffer
    -> GeometryFilter
ClosureSurface (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, klumMaterialClass xml_buffer, klumMaterialIndex xml_buffer, materialUncertainty xml_buffer, materialClass xml_buffer, materialName xml_buffer
    -> GeometryRemover
Note: The ClosureSurface are virtual and therefore not needed for the experiments.
GeometryRemover
    REMOVE_COORDSYS = No
    -> GeometryFilter
GeometryFilter
    FILTER_MODE = SIMPLE
    FILTER_MULTI = FILTER_TYPES]Null]FME_CONTROLLER_QUERY_FILE]]FME_CONTROLLER_CHOICE]Simple
    Null -> CoordinateSystemSetter
    <UNFILTERED> -> Offsetter
Note: The LOD3 building models were originally modeled in a different vertical reference system. After applying this offset, they align with the LOD2 building models from the State Mapping Agency.
Offsetter
    MODE_LOOKUP = CARTESIAN
    XOFF = 0
    YOFF = 0
    ZOFF = -46.47877
    MODE = Cartesian Coordinate
    OFFSET -> CoordinateSystemSetter
CoordinateSystemSetter
    COORDSYS = EPSG:25832
    -> NewFeatureType (writer CITYGML_4)
NewFeatureType (writer CITYGML_4)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, klumMaterialClass xml_buffer, klumMaterialIndex xml_buffer, materialUncertainty xml_buffer, materialClass xml_buffer, materialName xml_buffer, citygml_city_object_member{}.xlink_href xml_buffer, citygml_appearance_member{}.xlink_href xml_buffer, gml_feature_member{}.xlink_href xml_buffer, citygml_class xml_buffer, citygml_class_codeSpace xml_buffer, citygml_function{} xml_buffer, citygml_function{}.codeSpace xml_buffer, citygml_usage{} xml_buffer,
      citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_interior_room{}.xlink_href xml_buffer, citygml_consists_of_building_part{}.xlink_href xml_buffer, citygml_address{}.xlink_href xml_buffer, ade_noise_building_apartments xml_uint64, ade_noise_building_inhabitants xml_uint64, ade_noise_building_emission_points xml_buffer, ade_noise_building_Leq_day xml_real64, ade_noise_building_Leq_day_units xml_buffer, ade_noise_building_Lmax_day xml_real64, ade_noise_building_Lmax_day_units xml_buffer, ade_noise_building_Lmin_day xml_real64, ade_noise_building_Lmin_day_units xml_buffer, ade_noise_building_Leq_night xml_real64, ade_noise_building_Leq_night_units xml_buffer,
      ade_noise_building_Lmax_night xml_real64, ade_noise_building_Lmax_night_units xml_buffer, ade_noise_building_Lmin_night xml_real64, ade_noise_building_Lmin_night_units xml_buffer, ade_noise_building_reflection xml_buffer, ade_noise_building_reflection_correction xml_real64, ade_noise_building_reflection_correction_units xml_buffer, ade_noise_building_remark xml_buffer, dataAvailable xml_buffer, CreationDate xml_buffer, DataAvailable xml_buffer, creationDate xml_buffer, opendrive_dynamic xml_buffer, opendrive_id xml_buffer, opendrive_identifier_modelDate xml_buffer, opendrive_identifier_modelName xml_buffer, opendrive_identifier_modelVendor xml_buffer, opendrive_identifier_roadId xml_buffer, opendrive_identifier_roadObjectId xml_buffer, opendrive_identifier_roadObjectName xml_buffer, opendrive_identifier_sourceFileHashSha256 xml_buffer, opendrive_identifier_sourceFileName xml_buffer, opendrive_name xml_buffer, opendrive_orientation xml_buffer, opendrive_roadObject_dynamic xml_buffer, opendrive_roadObject_orientation xml_buffer, opendrive_roadObject_type xml_buffer, opendrive_road_length xml_buffer, opendrive_road_rule xml_buffer, opendrive_type xml_buffer,
      frameKlumMaterialClass xml_buffer, frameKlumMaterialIndex xml_buffer, frameMaterialClass xml_buffer, frameMaterialName xml_buffer, frameMaterialUncertainty xml_buffer, paneMaterialClass xml_buffer, _cityeditor_layer xml_buffer

Bookmark: Combination of the LOD2 models
Address (reader CITYGML_1)
    attributes: citygml_target_uri xml_buffer, citygml_feature_role xml_buffer, citygml_feature_role_attr_name xml_buffer, citygml_feature_role_attr_val xml_buffer, gml_description xml_buffer, gml_name xml_buffer, citygml_address xml_xml
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleLage xml_buffer, Gemeindeschluessel xml_buffer, Geometrietyp2DReferenz xml_buffer, Grundrissaktualitaet xml_buffer, HoeheDach xml_buffer,
      HoeheGrund xml_buffer, Methode xml_buffer, NiedrigsteTraufeDesGebaeudes xml_buffer
    -> FeatureMerger [REQUESTOR]
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> FeatureMerger [REQUESTOR]
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, Flaeche xml_buffer, Z_MAX xml_buffer, Z_MAX_ASL xml_buffer, Z_MIN xml_buffer, Z_MIN_ASL xml_buffer
    -> FeatureMerger [REQUESTOR]
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, Dachneigung xml_buffer, Dachorientierung xml_buffer, Flaeche xml_buffer, Z_MAX xml_buffer, Z_MAX_ASL xml_buffer, Z_MIN xml_buffer, Z_MIN_ASL xml_buffer
    -> FeatureMerger [REQUESTOR]
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, Flaeche xml_buffer, Z_MAX xml_buffer, Z_MAX_ASL xml_buffer, Z_MIN xml_buffer, Z_MIN_ASL xml_buffer
    -> FeatureMerger [REQUESTOR]
CSV (reader CSV2_1)
    attributes: ldbv_id varchar(19), lod3_building_id varchar(8)
    -> FeatureMerger [SUPPLIER]
    -> FeatureMerger_2 [SUPPLIER]
FeatureMerger
    ATTR_ACCUM_MODE = Merge Supplier
    ATTR_CONFLICT_RES_LOOKUP = REQUESTOR_IF_CONFLICT
    IGNORE_NULLS = No
    JOIN_KEYS = @Value(gml_parent_id) @Value(ldbv_id) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    UNMERGED_REQUESTOR -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(gml_id) @Value(ldbv_id) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    UNMERGED_REQUESTOR -> NewFeatureType (writer CITYGML_2)
NewFeatureType (writer CITYGML_2)
